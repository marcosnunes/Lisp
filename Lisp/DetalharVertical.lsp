(defun c:detalharvertical ()
  "Executa o comando -vbarun DETALHARVERTICAL a partir da linha de comando."
  (command "-vbarun" "DETALHARVERTICAL"))
(prompt "\nDigite DETALHARVERTICAL na linha de comando para gerar detalhamento de vertical")
